package GammaLib {
	import ScalarValues::*;
	
	calc def 'EF' {
		in op: Boolean;
		return : Boolean;
	}
	
	calc def 'AF' {
		in op: Boolean;
		return : Boolean;
	}
	
	calc def 'EG' {
		in op: Boolean;
		return : Boolean;
	}
	
	calc def 'AG' {
		in op: Boolean;
		return : Boolean;
	}
	
}
